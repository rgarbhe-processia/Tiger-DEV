Attribute VB_Name = "OpenCADFromFilteredBOM"
'===========================================================================================================
'===========================================================================================================
'                       CD5PartialOpenFromWeb.catvba Version 9
'
'===========================================================================================================
' This vba script could be launched
' 1) from web with using CD5PartialOpenFromWeb.vbs (version8)and arguments send by servlet
' 2) from CATIA is CD5PartialOpenFromWeb.txt file exists en CD5 local workspace folder
'
' Partial Open could be perform with using CD5Engine or V6Engine(>R2015xFD02) APIs according you CATIA release level
'
'===========================================================================================================

'CD5 Connector Variables
Public oCD5Engine
Public oV6Engine
Public oOpenOperation
'Public oOpenOperation As V6OpenOperation
Public V6Localfolder

Public FilterArray()
Public ExcludedObjects
Public NbObjects
Public NbIncluded
Public NbExcluded
Public StrFilePath As String
Public Timer1
Public Timer2
Public Timer3
Public FileList()
Public MyFile

Public NewAPI
Public Analysis
Public ExportList
Public ExpandMode
Public ShowPanel


Sub CATMain()
    OpenCADFromFilteredEBOM "File"
End Sub


'=================================================================================================
'   OpenCADFromFilteredEBOM
'===========================================================================================================
Sub OpenCADFromFilteredEBOM(myParam As String)

'Set ShowPanel = False to show open panel to execute open
ShowPanel = False

'Set NewAPI = False to force CD5Engine
NewAPI = True
'NewAPI = False

'Set Analysis = True to get Time result in msg box
Analysis = False
'Analysis = True

'Set ExportList = True to generate listObject in txt file in CD5 local workspace
ExportList = False
'ExportList = True

'Set ExpandMode = "RequiredChildren" to stop recursive method for V6Engine to CATPart
ExpandMode = "RequiredChildren"
ExpandMode = "AllChildren"

'Set CheckInstance = True to filter instance
CheckInstance = False
CheckInstance = True

ObjectSeparator = chr(10)
TNRSeparator = ","

On Error Resume Next
If NewAPI = True Then
    Set oV6Engine = CATIA.GetItem("V6Engine")
Else
    Set oV6Engine = CATIA.GetItem("NoV6Engine")
End If
If Err Then
    ConnectorEngine = "CD5Engine"
    If myParam = "File" Then
        Set oV6Engine = CATIA.GetItem("V6Engine")
        Set V6SettingsControllers = CATIA.SettingControllers
        Set V6Settings = V6SettingsControllers.Item("ENO3DEXPSettingCtrl")
        V6Localfolder = V6Settings.LocalWorkspaceLocation & "\"
    End If
Else
    ConnectorEngine = "V6Engine"
    Set V6SettingsControllers = CATIA.SettingControllers
    Set V6Settings = V6SettingsControllers.Item("ENO3DEXPSettingCtrl")
    V6Localfolder = V6Settings.LocalWorkspaceLocation & "\"
End If
On Error GoTo 0


'MsgBox "CD5PartialOpenInCATIAV5 macro" & myParam

ProgressBar.UpdateProgressBar 0.2
ProgressBar.SetPositionProgressBar
ProgressBar.Repaint
ProgressBar.Show
'MsgBox "OpenCADFromFilteredEBOM"
'Read Filter from 3DEXPERIENCE Server'

If myParam <> "File" Then

    pos = InStr(myParam, ":")
    Dim myURL
    Dim tmpParameters
        
    tmpParameters = Right(myParam, Len(myParam) - pos)
    aParameters = Split(tmpParameters, "&")
    myCookie = aParameters(0)
    myURL = aParameters(1)
    myTimeStamp = aParameters(2)
        
    Dim o
    Set o = CreateObject("Msxml2.ServerXMLHTTP.6.0")
    o.Open "GET", myURL & "/WebToWin?timestamp=" & myTimeStamp, False
    o.setRequestHeader "Cookie", myCookie
    On Error Resume Next
    o.Send
  
    If 200 <> o.Status Then
        MsgBox "Error while connecting to server : " & o.StatusText
        End
    End If
    
    Dim ListObjects
    ListObjects = o.responseText

Else
    
'   Set V6Localfolder = CATIA.FileSystem.GetFolder("D:\\Vasant\\OpenFilteredCAD\\")
'   nbfile = 0
'
'   For Each objFile In V6Localfolder.Files
'        If Right(objFile.Name, 4) = ".txt" Then
'            nbfile = nbfile + 1
'        End If
'    Next
'
'  'counts the .txt files and displays the same in popup window inside catia
'
'
'    If nbfile = 0 Then
'        MsgBox "No filter file in 3DEXPERIENCE LocalWorkspace (" & V6Localfolder & ")"
'    Else
'        ReDim FileList(nbfile - 1, 1)
'        nbfile = -1
'        For Each objFile In V6Localfolder.Files
'            If Right(objFile.Name, 4) = ".txt" Then
'                nbfile = nbfile + 1
'                FileList(nbfile, 0) = objFile.Path
'                FileList(nbfile, 1) = objFile.Name
'            End If
'        Next
'        nbfile = nbfile + 1
'
'        MyFile = ""
'
'        If nbfile = 1 Then
'            MyFile = FileList(0, 1)
'        Else
'            Load UserForm_Selection
'            UserForm_Selection.Show
'        End If
'
'    End If
'
'    If MyFile = "" Then End

'On Error Resume Next
Dim WSHShell
Dim TNRFilePath
Set WSHShell = CreateObject("WScript.Shell")
TNRFilePath = WSHShell.RegRead("HKEY_CURRENT_USER\OpenCADFromFilteredEBOM\TNRFilePath")

    
    Set FilterFile = CATIA.FileSystem.GetFile("" & TNRFilePath & "")
    Set FilterFileTextStream = FilterFile.OpenAsTextStream("ForReading")
    
    nbFilterFileLine = 0
    ListObjects = ""
    While FilterFileTextStream.AtEndOfStream = False
        FilterFileLine = FilterFileTextStream.ReadLine
        If Len(FilterFileLine) > 5 And Left(FilterFileLine, 1) <> "/" Then
            If Len(ListObjects) > 0 Then ListObjects = ListObjects & chr(10)
            ListObjects = ListObjects & FilterFileLine
        End If
    Wend
End If

'Define FilterLine Array from ListObjects String

NbLines = CountCharInString(ListObjects, chr(10)) + 1
    
FilterLineArray = Split(ListObjects, ObjectSeparator)
FilterLineArray = Array_Unique(FilterLineArray)
NbObjects = UBound(FilterLineArray) + 1

ReDim FilterArray(NbObjects, 5)

For i = LBound(FilterLineArray) To UBound(FilterLineArray)
    If InStr(FilterLineArray(i), ",") > 0 Then
        LineArray = Split(FilterLineArray(i), TNRSeparator)
        FilterArray(i, 0) = FilterLineArray(i)
        FilterArray(i, 1) = LineArray(0)
        FilterArray(i, 2) = LineArray(1)
        FilterArray(i, 3) = LineArray(2)
        On Error Resume Next
        FilterArray(i, 4) = LineArray(3)
        On Error GoTo 0
    
    End If
Next

'Open Operation

Timer1 = Time

If ConnectorEngine = "V6Engine" Then

    V6Engine

Else
    'MsgBox "Before calling CD5Engine from OpenCADFromFilteredEBOM"
    CD5Engine
    'MsgBox "after calling CD5Engine from OpenCADFromFilteredEBOM"
End If

Timer3 = Time

ProgressBar.UpdateProgressBar 0.9
ProgressBar.Repaint


If CheckInstance = True And ExportList = False Then

    DesactivateInstance

End If

ProgressBar.UpdateProgressBar 1
ProgressBar.Repaint

ProcessTime1 = DateDiff("s", Timer1, Timer2)
ProcessTime2 = DateDiff("s", Timer2, Timer3)
If Analysis = True Then MsgBox "Nb Included : " & NbIncluded & " / Nb Excluded " & NbExcluded & chr(10) & ConnectorEngine & " Select Items Time : " & ProcessTime1 & " seconds" & chr(10) & ConnectorEngine & " Open Time : " & ProcessTime2 & " seconds"

ProgressBar.Hide

If ExportList = True Then
MsgBox "ExportList True"
    ListObjectFileName = FilterArray(0, 2) & "_Filter" & NbIncluded & ".txt"
    ListObjectFilePath = V6Localfolder & ListObjectFileName
    Dim fso As Object
    Set fso = CreateObject("Scripting.FileSystemObject")
    Dim oFile As Object
    If fso.FileExists(ListObjectFilePath) Then
        fso.DeleteFile V6Localfolder & ListObjectFileName, True
    End If
    Set oFile = fso.CreateTextFile(ListObjectFilePath, True)
    For i = LBound(FilterLineArray) To UBound(FilterLineArray)
        If InStr(FilterLineArray(i), ",") > 0 Then
            ListObjectLine = FilterArray(i, 1) & TNRSeparator & FilterArray(i, 2) & TNRSeparator & FilterArray(i, 3) & TNRSeparator & FilterArray(i, 4)
            oFile.WriteLine ListObjectLine
        End If
    Next
    oFile.Close
End If
'MsgBox "CAD Objects are Opened from Filtered EBOM"

End Sub

Sub DesactivateInstance()

Dim productDocument1 As Document
Dim documents1 As Documents
Dim product1 As Product
Dim selection1 As Selection

Err.Clear
On Error Resume Next
Set productDocument1 = CATIA.ActiveDocument
If Err <> 0 Then
    MsgBox "CATIA session not available"
    End
End If

RootFileName = Mid(productDocument1.Name, 1, InStrRev(productDocument1.Name, ".") - 1)
RootPath = "\" & RootFileName


RecursiveDesactivation productDocument1.Product, RootPath

End Sub

Sub RecursiveDesactivation(ProductRef, ProductPath)

For Each SubProduct In ProductRef.Products

    On Error Resume Next
    Set SubReference = SubProduct.ReferenceProduct
    NbSubReferenceProducts = SubReference.Products.Count
    If Err = 0 Then
        SubReferenceDocName = SubReference.Name
        SubProductPath = ProductPath & "\" & SubProduct.Name
        RecursiveDesactivation SubProduct, SubProductPath
    Else
        InstancePath = ProductPath & "\" & SubProduct.Name
        Activation = False
    
        For k = 1 To UBound(FilterArray)
            IObjectPath = FilterArray(k, 4)
            
            If FilterArray(k, 1) = "" Then Exit For
    
            If IObjectPath = InstancePath Or IObjectPath = "" Then
                Activation = True
                Exit For
            End If
    
        Next
        
        If Activation = False Then
            SubProduct.DesactivateDefaultShape
        End If
        
    End If
    On Error GoTo 0


Next


End Sub

Sub CD5Engine()

Set oCD5Engine = CATIA.GetItem("CD5Engine")

oCD5Engine.IncludeAllChildren = False
oCD5Engine.RelatedDesigns = "None"
oCD5Engine.ExpandMode = "As-Built"

TRoot = FilterArray(0, 1)
NRoot = FilterArray(0, 2)
RRoot = FilterArray(0, 3)

' Create ID of Root Product and get access to the associated structure
'Dim RootID
Set RootID = oCD5Engine.GetIDFromTNR(TRoot, NRoot, RRoot)

'Set RootID = oCD5Engine.GetIDFromTNR("PSS_CATPart", "PUNPRT02", "-A")
'Dim myStructure
Set myStructure = oCD5Engine.GetStructure(RootID)

NbIncluded = 1

'Dim subNodeID
For k = 0 To UBound(FilterArray) - 1

    TObject = FilterArray(k, 1)
    NObject = FilterArray(k, 2)
    RObject = FilterArray(k, 3)
    If Len(TObject) > 5 Then
        Set subNodeID = oCD5Engine.GetIDFromTNR(TObject, NObject, RObject)
        myStructure.Include subNodeID
        If NbIncluded < NbObjects Then NbIncluded = 1 + NbIncluded
        ProgressBar.UpdateProgressBar (0.3 + 0.5 * NbIncluded / NbObjects)
        ProgressBar.Repaint
    End If
    
Next

Timer2 = Time

On Error Resume Next
oCD5Engine.PartialOpen (myStructure)
If Err Then
    MsgBox Err.Description
End If

End Sub


Sub V6Engine()

NbExcluded = 0
ExcludedObjects = ""

TRoot = FilterArray(0, 1)
NRoot = FilterArray(0, 2)
RRoot = FilterArray(0, 3)
MsgBox "V6Engine code starts"
Set RootID = oV6Engine.GetIDFromTNR(TRoot, NRoot, RRoot)
MsgBox RootID
Set oOpenOperation = oV6Engine.CreateOpenOperation()

oOpenOperation.ExpandMode = "As-Built"
oOpenOperation.IncludeAllChildren = False

oOpenOperation.AddRoot (RootID)
FilterArray(0, 5) = "Done"
NbIncluded = 1
ProgressBar.UpdateProgressBar (0.3 + 0.5 * NbIncluded / NbObjects)
ProgressBar.Repaint

Set oOpenRootItems = oOpenOperation.RootItems

For i = 1 To oOpenRootItems.Count

    Set oCurrentRootItem = oOpenRootItems.Item(i)
    oCurrentRootIncluded = True
    
    RecursiveExpandStructure oCurrentRootItem, oCurrentRootIncluded

Next

NbExcluded = CountCharInString(ExcludedObjects, ".")

Timer2 = Time
If ShowPanel = False Then
    oOpenOperation.Run
Else
    oOpenOperation.ShowPanel
End If
MsgBox "V6 Engine function ends"
End Sub


'===========================================================================================================
'   RecursiveExpandStructure for V6 Engine
'===========================================================================================================
Sub RecursiveExpandStructure(oV6SubItem, oV6SubIncluded)

    Set oCurrentItems = oV6SubItem.Items
    
    If oCurrentItems.Count > 0 Then

        For j = 1 To oCurrentItems.Count
        
            Set oCurrentSubItem = oCurrentItems.Item(j)
            
            If oCurrentSubItem.Included Then
            
                Set oCurrentSubItemID = oCurrentSubItem.V6ID
                CurrentName = oCurrentSubItemID.N
                CurrentType = oCurrentSubItemID.t
                Included = False
                
                For k = 0 To UBound(FilterArray)
                    If FilterArray(k, 1) = CurrentType And FilterArray(k, 2) = CurrentName Then
                        Included = True
                        
                        If FilterArray(k, 5) <> "Done" Then
                            oCurrentSubItem.Included = True
                            FilterArray(k, 5) = "Done"
                            If NbIncluded < NbObjects Then NbIncluded = 1 + NbIncluded
                            ProgressBar.UpdateProgressBar (0.3 + 0.5 * NbIncluded / NbObjects)
                            ProgressBar.Repaint
                            If oCurrentSubItem.Items.Count > 0 Then
                                'On Error Resume Next
                                RecursiveExpandStructure oCurrentSubItem, oCurrentSubItem.Included
                            End If
                        End If
                        
                            
                        Exit For
                    End If
                
                Next
                
                If Not Included Then
                    oCurrentSubItem.Included = False
                    CurrentFile = CurrentName & "." & CurrentType
                    If oCurrentSubItem.Items.Count > 0 And CurrentType <> "CATPart" And InStr(ExcludedObjects, CurrentFile) = 0 Then
                        'Start condition to stop recursive method
                        If ExpandMode <> "RequiredChildren" And CurrentType <> "CATPart" Then
                            RecursiveExpandStructure oCurrentSubItem, oCurrentSubItem.Included
                        End If
                        'End condition to stop recursive method
                    End If
                    ExcludedObjects = CurrentFile & chr(10) & ExcludedObjects
                End If
            
            End If
            
        Next
    
    End If


End Sub

Sub SelectFile()


Load UserForm_Selection
UserForm_Selection.Show


End Sub

Function Array_Unique(arr As Variant) As Variant
  Dim tempArray As Variant
  Dim i As Long
 
  ' start the temp array with one element and
  ' populate with first value
  ReDim tempArray(0)
  tempArray(0) = arr(LBound(arr))
 
  For i = LBound(arr) To UBound(arr)
    If Not IsInArray(tempArray, arr(i)) Then  ' not in destination array
      ReDim Preserve tempArray(UBound(tempArray) + 1)
      tempArray(UBound(tempArray)) = arr(i)
    End If
  Next i
 
  Array_Unique = tempArray
End Function

Function IsInArray(arr As Variant, valueToCheck As Variant) As Boolean
   IsInArray = (UBound(Filter(arr, valueToCheck)) > -1)
End Function

Function CountCharInString(str, chr)

Nbchar = 0
For i = 1 To Len(str)
    ch1 = Mid(str, i, 1)
    If ch1 = chr Then
        Nbchar = Nbchar + 1
    End If
Next
CountCharInString = Nbchar

End Function

Attribute VB_Name = "ProgressBar"
Attribute VB_Base = "0{FA8B9C59-B227-43A5-90F6-C3119F0FA359}{BD529B37-7B0B-4AB0-9B7C-31F33442F806}"
Attribute VB_GlobalNameSpace = False
Attribute VB_Creatable = False
Attribute VB_PredeclaredId = True
Attribute VB_Exposed = False
Attribute VB_TemplateDerived = False
Attribute VB_Customizable = False


Public blContinue As Boolean
Public flag As Boolean

Sub ProgressBarValue(ByVal sPercent As Single)
    ProgressBar.Image2.Width = sPercent * 308
End Sub

Sub UpdateProgressBar(ByVal sPercent As Single)
    ProgressBarValue sPercent
    ProgressBar.Repaint
End Sub



Public Sub SetPositionProgressBar()

ProgressBar.Left = 3 / 4 * (CATIA.Left + CATIA.Width) - (ProgressBar.Width + 70)
ProgressBar.Top = 3 / 4 * (CATIA.Top + CATIA.Height) - (ProgressBar.Height + 70)
'On Error Resume

End Sub

Private Sub UserForm_Activate()
    On Error Resume Next
    RetStr = t.Test(100000)
    ProgressBar.SetPositionProgressBar
    Dim i As Integer
    blTerminate = False
End Sub

Private Sub UserForm_Terminate()
    'blTerminate = True
    blContinue = False
    'Unload Me
End Sub

Attribute VB_Name = "UserForm_Selection"
Attribute VB_Base = "0{E0E8161E-BAF7-47D6-A135-10042E4EE2F9}{0B375088-72DC-4523-82B5-A5743D476B2E}"
Attribute VB_GlobalNameSpace = False
Attribute VB_Creatable = False
Attribute VB_PredeclaredId = True
Attribute VB_Exposed = False
Attribute VB_TemplateDerived = False
Attribute VB_Customizable = False

Private Sub ListFiles_DblClick(ByVal Cancel As MSForms.ReturnBoolean)
        
    i = ListFiles.ListIndex
    
    MyFile = FileList(i, 1)
    
    Unload UserForm_Selection
    
End Sub


Private Sub UserForm_Initialize()
   
Dim ListArray()
ReDim ListArray(UBound(FileList), 1)

Folder.Caption = V6Localfolder

For k = 0 To UBound(FileList)
    
    ListArray(k, 0) = k + 1
    ListArray(k, 1) = FileList(k, 1)

Next

ListFiles.List() = ListArray

End Sub



Private Sub CommandCancel_Click()

Unload UserForm_Selection

End Sub
